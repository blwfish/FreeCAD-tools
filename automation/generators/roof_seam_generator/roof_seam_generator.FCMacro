"""
Roof Seam Generator for FreeCAD v2.0.0
Generates hip cap shingles or valley flashing between two selected roof faces.

Author: Brian (with Claude assistance)
Usage: Ctrl+click two adjacent roof faces, run as macro in FreeCAD

Version History:
- 1.7.0: Narrow hip caps to half width (cap_width/4 per side). Extend
         halves past seam so exterior surfaces overlap at the hip ridge,
         closing the V-groove between slopes. Remove face-extrusion
         clipping which was trimming at the seam edge, preventing overlap.
- 1.6.0: Lift hip caps above roof surface by materialThickness so they
         sit on top of the field shingles rather than at the bare roof plane.
         Without this offset, tapered field shingles (v5.2.0) are thicker
         than the caps' placement plane, burying the caps.
- 1.5.1: Fix taper direction for inward-Z halves. When outward=False the Z
         axis points into the roof, so the Z=0 face is the visible exterior.
         make_tapered_box() now accepts taper_top: True puts taper on Z=max
         (outward case), False puts taper on Z=0 (inward case) so the
         shadow-line is always on the exterior face.
- 1.5.0: Replace cumulative stagger with tapered cap profile. Each cap is
         a wedge: full mat_thick at the exposed butt edge, tapering to 20%
         at the covered top edge. The taper creates a visible shadow-line
         at each butt edge in STL without cumulative lift-off. Removed
         bisector stagger entirely.
- 1.4.1: Fix wishbone splitting at apex. Stagger was offset along each
         face's individual normal, so the two halves diverged as the
         cumulative offset grew. Now offsets along the bisector of the
         two face normals — both halves rise together.
- 1.4.0: Stagger hip caps and close ridge channel.
         1) Each half extends mat_thick past the ridge so the two halves
            overlap at the seam, closing the V-groove between slopes.
         2) Edge iteration runs eave→apex (low Z to high Z). Each
            successive cap is offset by mat_thick along the face normal,
            creating the visible overlap/stagger that makes individual
            cap shingles distinguishable in STL export.
         Clip solid extrusion scaled to encompass the full stagger stack.
- 1.3.1: Fix fuse-invalid after clipping. The clip solid was extruded by
         exactly mat_thick, making its top/bottom faces coplanar with the cap
         → degenerate edges from common() → "Resulting shape is invalid" on
         fuse. Now extrudes 3× mat_thick so the clip fully envelops the cap
         in the normal direction; clipping only acts in the face plane.
- 1.3.0: Clip hip cap halves to roof face boundaries. Each roof face is
         extruded by materialThickness along its normal to create a clipping
         solid; boolean intersection trims half-caps that overhang the eave
         at the bottom of hip seams. Caps fully outside the face are dropped.
- 1.2.1: Fix rotation handedness bug in hip cap halves. When d is sign-flipped
         to point toward the face interior, {d, edge_dir, n} becomes left-handed,
         producing a reflection that flips one half 180°. Now computes Z axis as
         d.cross(edge_dir) (always right-handed) and offsets the corner by
         mat_thick along n when Z points inward.
- 1.2.0: Redesign hip cap geometry. Each cap position now produces two
         half-shingles, one per face, each lying flat on its slope and
         meeting at the shared edge. The previous single flat box floated
         above the roof surface on any seam with a significant slope angle.
- 1.1.2: Fix face-matching metric in closest_base_face(). Centroid-to-centroid
         distance was picking eave/soffit faces instead of slope faces for
         shingles near the hip seam. Now uses distToShape() (point-to-surface
         distance): the shingle's centroid lies on the slope surface it was
         generated from, so surface dist ≈ 0 for the correct face and >> 0
         for all others.
- 1.1.1: Fix wrong-seam selection when both ShingledRoof compounds share the
         same BaseObject (e.g. two slopes of the same roof solid). The old
         brute-force search over all BaseObject face pairs found the first
         shared edge in the solid rather than the one near the selected
         shingles. Now uses centroid proximity to map each selected shingle
         face to its closest BaseObject roof-plane face, then checks only
         that specific pair.
- 1.1.0: Auto-unwrap ShingledRoof compounds via BaseObject so the macro works
         when the user clicks on individual shingle faces rather than the
         original roof faces. resolve_shared_edge() tries raw faces first,
         then falls back to all BaseObject-face pairs.
- 1.0.2: Add face vertex/edge diagnostic dump to "no shared edge" error.
- 1.0.1: Replace sys.exit() with if/else (FreeCAD macro best practice).
         Add raw selection dump to the "wrong face count" error so the cause
         (e.g. selection cleared by Macros dialog, or whole-object selected
         instead of face sub-elements) is immediately visible in the log.
- 1.0.0: Initial release.
         Auto-detects hip vs valley from Z coordinates:
           Hip/ridge: non-shared vertices are BELOW the shared edge
                      → cap shingles at exposure intervals straddling the edge
           Valley: non-shared vertices are ABOVE the shared edge
                   → single flat flashing strip along full edge length

         IMPORTANT: Uses * operator (not .multiply()) for all vector scaling
         because App.Vector.multiply() mutates the vector in place.

Parameters read from spreadsheet (falls back to defaults if not found):
    shingleWidth          — used as default for hipCapWidth
    shingleHeight         — height of each hip cap shingle
    materialThickness     — thickness of cap/flashing; default for valleyFlashingWidth
    shingleExposure       — spacing between hip cap shingles
    hipCapWidth           — width of hip cap (default: shingleWidth)
    valleyFlashingWidth   — width of valley flashing (default: materialThickness * 8)

Output:
    HipCap_{objectName}          — compound of cap shingles (hip/ridge)
    ValleyFlashing_{objectName}  — compound of flashing strip (valley)
"""

import FreeCAD as App
import FreeCADGui as Gui
import Part
from FreeCAD import Vector
import math
import os
import sys
sys.path.insert(0, os.path.join(App.getUserMacroDir(True), "_lib"))
from freecad_utils import commit_result

VERSION = "2.0.2"
GENERATOR_NAME = "roof_seam_generator"


# ============================================================================
# Spreadsheet parameter loading
# ============================================================================

def find_spreadsheet(doc):
    """Find spreadsheet by name or label, following App::Link if needed."""
    preferred_names = ["params", "ShingleParameters", "BuildingParameters", "Spreadsheet"]
    for ss_name in preferred_names:
        obj = doc.getObject(ss_name)
        if obj:
            if obj.TypeId == 'App::Link':
                target = obj.LinkedObject
                if target and target.TypeId == 'Spreadsheet::Sheet':
                    return target
            elif obj.TypeId == 'Spreadsheet::Sheet':
                return obj
        for obj in doc.Objects:
            if obj.Label == ss_name:
                if obj.TypeId == 'App::Link':
                    target = obj.LinkedObject
                    if target and target.TypeId == 'Spreadsheet::Sheet':
                        return target
                elif obj.TypeId == 'Spreadsheet::Sheet':
                    return obj
    return None


def get_params_from_spreadsheet(doc):
    """Read seam generator parameters from spreadsheet. Returns {} if not found."""
    ss = find_spreadsheet(doc)
    if ss is None:
        return {}

    params = {}
    aliases = {
        'shingleWidth':         ['shingleWidth'],
        'shingleHeight':        ['shingleHeight'],
        'materialThickness':    ['materialThickness'],
        'shingleExposure':      ['shingleExposure', 'exposure'],
        'hipCapWidth':          ['hipCapWidth'],
        'valleyFlashingWidth':  ['valleyFlashingWidth'],
    }

    for key, names in aliases.items():
        for name in names:
            try:
                val = ss.get(name)
                if val is not None:
                    params[key] = float(val)
                    break
            except Exception:
                continue

    return params


# ============================================================================
# Geometry helpers
# ============================================================================

def find_shared_edge(face1, face2, tol=0.01):
    """Find the shared edge between two faces by matching endpoint positions."""
    for e1 in face1.Edges:
        p1a = e1.Vertexes[0].Point
        p1b = e1.Vertexes[-1].Point
        for e2 in face2.Edges:
            p2a = e2.Vertexes[0].Point
            p2b = e2.Vertexes[-1].Point
            if ((p1a.distanceToPoint(p2a) < tol and p1b.distanceToPoint(p2b) < tol) or
                    (p1a.distanceToPoint(p2b) < tol and p1b.distanceToPoint(p2a) < tol)):
                return e1
    return None


def classify_seam(face1, face2, shared_edge):
    """
    Classify the shared edge as 'hip' or 'valley' using Z-coordinate analysis.

    Valley: non-shared vertices are ABOVE the shared edge
            (they're at the eaves; the shared edge is the valley bottom)
    Hip:    non-shared vertices are BELOW the shared edge
            (they're at the eaves; the shared edge is the hip peak or ridge)
    """
    edge_verts = [v.Point for v in shared_edge.Vertexes]
    edge_max_z = max(p.z for p in edge_verts)

    # Build set of positions that lie on the shared edge (rounded for tolerance)
    shared_pts = set()
    for p in edge_verts:
        shared_pts.add((round(p.x, 2), round(p.y, 2), round(p.z, 2)))

    non_shared_z = []
    for face in (face1, face2):
        for v in face.Vertexes:
            key = (round(v.Point.x, 2), round(v.Point.y, 2), round(v.Point.z, 2))
            if key not in shared_pts:
                non_shared_z.append(v.Point.z)

    if not non_shared_z:
        App.Console.PrintMessage("  WARNING: Could not find non-shared vertices, defaulting to hip\n")
        return 'hip'

    avg_z = sum(non_shared_z) / len(non_shared_z)

    App.Console.PrintMessage(f"  Shared edge max Z:      {edge_max_z:.3f} mm\n")
    App.Console.PrintMessage(f"  Non-shared vertices avg Z: {avg_z:.3f} mm\n")

    if avg_z > edge_max_z:
        return 'valley'
    else:
        return 'hip'


def closest_base_face(orig_face, base_faces):
    """
    Return the face in base_faces whose SURFACE is closest to orig_face's
    centroid point.

    The shingle was extruded from the roof slope, so its centroid lies
    essentially on (or very near) that slope's surface — surface distance
    ≈ 0.  Centroid-to-centroid distance is unreliable because a small
    shingle near an edge can be much farther from the slope-face centre than
    from the centre of an adjacent eave/soffit face.
    """
    orig_center = orig_face.CenterOfMass
    test_vtx = Part.Vertex(orig_center)
    best = None
    best_dist = float('inf')
    for f in base_faces:
        try:
            d = f.distToShape(test_vtx)[0]
        except Exception:
            # Fall back to centroid distance if distToShape fails
            d = orig_center.distanceToPoint(f.CenterOfMass)
        if d < best_dist:
            best_dist = d
            best = f
    App.Console.PrintMessage(f"    → best base face surface dist: {best_dist:.4f} mm\n")
    return best


def resolve_shared_edge(face1, obj1, face2, obj2):
    """
    Find the shared edge between two faces, automatically unwrapping
    ShingledRoof compounds to their BaseObject faces when needed.

    When the user clicks on shingles (not on the original roof geometry),
    the selected faces are individual shingle-box faces from a ShingledRoof
    compound.  Those shingles don't share edges with each other.  But the
    compound has a BaseObject property pointing to the original roof shape
    whose faces DO share the hip/valley edge.

    Strategy:
      1. Try the raw selected faces (fast path — works if user selected from
         the original roof geometry).
      2. If either object is a ShingledRoof compound, find the single
         BaseObject face closest (by centroid) to each selected shingle face,
         then check just that pair.  Proximity correctly maps each shingle to
         the roof plane it sits on — avoiding the wrong-edge problem that
         occurs when brute-forcing all face pairs of the same base solid.

    Returns:
        (shared_edge, resolved_face1, resolved_obj1, resolved_face2, resolved_obj2)
        or (None, face1, obj1, face2, obj2) if no shared edge found.
    """
    # Fast path: raw faces share an edge directly
    edge = find_shared_edge(face1, face2)
    if edge is not None:
        return edge, face1, obj1, face2, obj2

    # Unwrap each compound to its single best-matching BaseObject face
    def get_base(face, obj):
        if (obj.TypeId == 'Part::Compound'
                and hasattr(obj, 'BaseObject')
                and obj.BaseObject is not None):
            base = obj.BaseObject
            App.Console.PrintMessage(
                f"  Unwrapping {obj.Name} → BaseObject={base.Name}"
                f" ({len(base.Shape.Faces)} face(s))\n"
            )
            return closest_base_face(face, base.Shape.Faces), base
        return face, obj

    f1, o1 = get_base(face1, obj1)
    f2, o2 = get_base(face2, obj2)

    if f1 is not face1 or f2 is not face2:
        edge = find_shared_edge(f1, f2)
        if edge is not None:
            App.Console.PrintMessage("  Found shared edge via BaseObject resolution\n")
            return edge, f1, o1, f2, o2

    return None, face1, obj1, face2, obj2


def face_normal_at_center(face):
    """Return the face normal at its parametric center."""
    uv = face.ParameterRange
    u_mid = (uv[0] + uv[1]) / 2.0
    v_mid = (uv[2] + uv[3]) / 2.0
    return face.normalAt(u_mid, v_mid)


def make_rotation_matrix(x_axis, y_axis, z_axis):
    """
    Build a rotation matrix from three orthogonal basis vectors (column convention).
    Box local X → x_axis, local Y → y_axis, local Z → z_axis.
    """
    return App.Matrix(
        x_axis.x, y_axis.x, z_axis.x, 0,
        x_axis.y, y_axis.y, z_axis.y, 0,
        x_axis.z, y_axis.z, z_axis.z, 0,
        0, 0, 0, 1
    )


def make_tapered_box(width, height, butt_thick, top_thick, taper_top=True):
    """
    Create a box tapered in Z along the Y axis.

    At Y=0 (the exposed butt edge) the box is butt_thick tall.
    At Y=height (the covered top edge) it is top_thick tall.

    taper_top=True  (outward Z): flat bottom at Z=0, top tapers down.
    taper_top=False (inward Z):  flat top at Z=butt_thick, bottom tapers up.

    This taper creates the visible shadow-line at each butt edge
    that makes individual shingles/caps distinguishable in STL export,
    without needing cumulative stagger.
    """
    if taper_top:
        # Standard: flat bottom, tapered top
        p0 = Vector(0, 0, 0)
        p1 = Vector(width, 0, 0)
        p2 = Vector(width, height, 0)
        p3 = Vector(0, height, 0)
        p4 = Vector(0, 0, butt_thick)
        p5 = Vector(width, 0, butt_thick)
        p6 = Vector(width, height, top_thick)
        p7 = Vector(0, height, top_thick)
    else:
        # Reversed: flat top, tapered bottom (taper visible on Z=0 face)
        taper_rise = butt_thick - top_thick
        p0 = Vector(0, 0, 0)
        p1 = Vector(width, 0, 0)
        p2 = Vector(width, height, taper_rise)
        p3 = Vector(0, height, taper_rise)
        p4 = Vector(0, 0, butt_thick)
        p5 = Vector(width, 0, butt_thick)
        p6 = Vector(width, height, butt_thick)
        p7 = Vector(0, height, butt_thick)

    def _face(pts):
        edges = [Part.makeLine(pts[i], pts[(i + 1) % len(pts)])
                 for i in range(len(pts))]
        return Part.Face(Part.Wire(edges))

    shell = Part.makeShell([
        _face([p0, p1, p2, p3]),  # bottom
        _face([p7, p6, p5, p4]),  # top (reversed for outward normal)
        _face([p0, p1, p5, p4]),  # front — butt edge
        _face([p3, p7, p6, p2]),  # back  — covered edge
        _face([p0, p4, p7, p3]),  # left
        _face([p1, p2, p6, p5]),  # right
    ])
    return Part.makeSolid(shell)


# ============================================================================
# Cap shingle generation (hip / ridge)
# ============================================================================

def generate_hip_caps(shared_edge, face1, face2, params):
    """
    Generate cap shingles straddling the hip/ridge edge.

    Each cap position produces TWO half-shingles that each lie flat on their
    respective face and meet at the shared edge.  This avoids the "floating
    flat slab" problem that occurs when a single rectangular box is placed in
    the bisector plane of a steep diagonal hip seam.

    Coordinate system per half (guaranteed right-handed):
      X = d  — away from seam toward face interior (sign-corrected)
      Y = edge_dir — along the shared edge
      Z = d × edge_dir — perpendicular to X and Y

    When d is sign-flipped (to point toward the face interior), Z may end up
    pointing inward (−n) instead of outward (+n).  In that case the box
    corner is offset outward by materialThickness so the box still sits on
    top of the face surface.
    """
    cap_width    = params.get('hipCapWidth', params.get('shingleWidth', 3.5))
    cap_height   = params.get('shingleHeight', 2.0)
    mat_thick    = params.get('materialThickness', 0.25)
    wedge_thick  = params.get('shingleWedgeThickness', mat_thick * 3)
    exposure     = params.get('shingleExposure', 1.5)
    butt_thick   = mat_thick
    top_thick    = mat_thick * 0.2
    half_width   = cap_width / 2.0
    cap_lift     = mat_thick

    App.Console.PrintMessage(
        f"Hip cap: width={cap_width:.2f}  height={cap_height:.2f}  "
        f"thickness={mat_thick:.2f}  exposure={exposure:.2f}  "
        f"lift={cap_lift:.2f}  half_width={half_width:.2f}\n"
    )

    # Edge geometry — orient so we iterate from eave (low Z) to apex (high Z).
    v0 = shared_edge.Vertexes[0].Point
    v1 = shared_edge.Vertexes[-1].Point
    if v0.z <= v1.z:
        start_pt, end_pt = v0, v1
    else:
        start_pt, end_pt = v1, v0
    edge_vec   = end_pt - start_pt
    edge_len   = edge_vec.Length
    edge_dir   = edge_vec * (1.0 / edge_len)

    # Outward face normals (positive Z for non-vertical roofs).
    n1 = face_normal_at_center(face1)
    n2 = face_normal_at_center(face2)
    n1_out = App.Vector(-n1.x, -n1.y, -n1.z) if n1.z < 0 else App.Vector(n1.x, n1.y, n1.z)
    n2_out = App.Vector(-n2.x, -n2.y, -n2.z) if n2.z < 0 else App.Vector(n2.x, n2.y, n2.z)

    seam_mid = (start_pt + end_pt) * 0.5

    # d1, d2: directions from seam toward each face interior,
    # perpendicular to edge, in the face plane.
    def compute_d(n_out, face_centroid):
        d_raw = n_out.cross(edge_dir)
        d = d_raw * (1.0 / d_raw.Length)
        if (face_centroid - seam_mid).dot(d) < 0:
            d = d * -1.0
        return d

    d1 = compute_d(n1_out, face1.CenterOfMass)
    d2 = compute_d(n2_out, face2.CenterOfMass)

    # Bisector of outward normals — used for ridge lift.
    bisector = n1_out + n2_out
    bisector = bisector * (1.0 / bisector.Length)

    App.Console.PrintMessage(
        f"  edge_dir: ({edge_dir.x:.3f}, {edge_dir.y:.3f}, {edge_dir.z:.3f})\n"
        f"  n1_out:   ({n1_out.x:.3f}, {n1_out.y:.3f}, {n1_out.z:.3f})\n"
        f"  n2_out:   ({n2_out.x:.3f}, {n2_out.y:.3f}, {n2_out.z:.3f})\n"
        f"  d1:       ({d1.x:.3f}, {d1.y:.3f}, {d1.z:.3f})\n"
        f"  d2:       ({d2.x:.3f}, {d2.y:.3f}, {d2.z:.3f})\n"
    )

    def make_bent_profile(pt, thickness):
        """
        Create a bent cross-section wire at position pt along the edge.

        The profile is a V-shape (following both roof slopes) with
        thickness offset perpendicular to each slope.  An arc at the
        ridge connects the two exterior surfaces with a gentle dome,
        eliminating the V-groove that two separate halves would create.

        Cross-section points:
          bl  — face 1 wing tip, on roof surface
          bc  — ridge/seam, on roof surface (V bottom)
          br  — face 2 wing tip, on roof surface
          tr  — face 2 wing tip, exterior
          tc2 — ridge exterior, face 2 side (arc endpoint)
          tc1 — ridge exterior, face 1 side (arc endpoint)
          tl  — face 1 wing tip, exterior

        The ridge arc from tc2 → tc1 replaces a flat segment, matching
        the reference cap-profile model.
        """
        # Lift each wing along its face normal; lift ridge along bisector.
        lift1 = n1_out * cap_lift
        lift2 = n2_out * cap_lift
        lift_c = bisector * cap_lift

        # Bottom points (on roof surface, lifted above field shingles)
        bl = pt + d1 * half_width + lift1
        bc = pt + lift_c
        br = pt + d2 * half_width + lift2

        # Top points (exterior, offset perpendicular to each slope)
        tl  = bl + n1_out * thickness
        tc1 = bc + n1_out * thickness
        tc2 = bc + n2_out * thickness
        tr  = br + n2_out * thickness

        # Ridge arc: gentle dome connecting tc2 → tc1.
        # Midpoint sits above the chord midpoint along the bisector.
        chord_mid = (tc1 + tc2) * 0.5
        sagitta = thickness * 1.0
        arc_mid = chord_mid + bisector * sagitta

        # Build wire from line edges + arc
        edges = [
            Part.makeLine(bl, bc),
            Part.makeLine(bc, br),
            Part.makeLine(br, tr),
            Part.makeLine(tr, tc2),
            Part.Arc(tc2, arc_mid, tc1).toShape(),
            Part.makeLine(tc1, tl),
            Part.makeLine(tl, bl),
        ]
        wire = Part.Wire(edges)
        return wire

    # Clipping solid: union of both face extrusions for eave trimming.
    clip_thick = butt_thick * 5.0 + cap_lift
    clip1 = face1.extrude(n1_out * clip_thick)
    clip2 = face2.extrude(n2_out * clip_thick)
    clip_union = clip1.fuse(clip2).removeSplitter()

    # Verify normals are perpendicular to edge (required for planar profiles).
    dot1 = n1_out.dot(edge_dir)
    dot2 = n2_out.dot(edge_dir)
    App.Console.PrintMessage(
        f"  n1_out·edge_dir={dot1:.6f}  n2_out·edge_dir={dot2:.6f}\n"
    )

    shapes = []
    clipped_count = 0
    loft_ok = 0
    loft_fail = 0
    extrude_ok = 0
    t = 0.0
    while t < edge_len:
        pt = start_pt + edge_dir * t

        # Two profile wires: butt (thick) and covered (thin).
        butt_wire = make_bent_profile(pt, butt_thick)
        covered_wire = make_bent_profile(pt + edge_dir * cap_height, top_thick)

        # Loft between thick butt and thin covered profiles for taper.
        # Extrude fallback gives constant thickness (no taper).
        cap = None
        try:
            cap = Part.makeLoft([butt_wire, covered_wire], True)
            loft_ok += 1
        except Exception as e:
            if t == 0.0:
                App.Console.PrintMessage(f"  Loft failed: {e}\n")
                # Dump wire info
                App.Console.PrintMessage(
                    f"  butt_wire: {len(butt_wire.Edges)} edges, closed={butt_wire.isClosed()}\n"
                    f"  covered_wire: {len(covered_wire.Edges)} edges, closed={covered_wire.isClosed()}\n"
                )

        if cap is None:
            try:
                butt_face = Part.Face(butt_wire)
                cap = butt_face.extrude(edge_dir * cap_height)
                extrude_ok += 1
            except Exception:
                loft_fail += 1
                t += exposure
                clipped_count += 1
                continue

        # Diagnostic on first cap
        if t == 0.0:
            bb = cap.BoundBox
            App.Console.PrintMessage(
                f"  First cap: vol={cap.Volume:.6f} solids={len(cap.Solids)} "
                f"faces={len(cap.Faces)} "
                f"bbox=[{bb.XMin:.2f},{bb.XMax:.2f}]x"
                f"[{bb.YMin:.2f},{bb.YMax:.2f}]x"
                f"[{bb.ZMin:.2f},{bb.ZMax:.2f}]\n"
            )

        # Add cap directly — no clipping.  The bent profile already
        # conforms to both face slopes so clipping is unnecessary,
        # and common(clip_union) splits the dome at the ridge seam.
        if cap.Solids:
            for solid in cap.Solids:
                shapes.append(solid)
        elif cap.Volume > 1e-6:
            shapes.append(cap)

        t += exposure

    App.Console.PrintMessage(
        f"  Cap creation: extrude={extrude_ok} loft={loft_ok} fail={loft_fail}\n"
    )

    if clipped_count:
        App.Console.PrintMessage(f"  Clipped away {clipped_count} caps outside face boundary\n")

    App.Console.PrintMessage(
        f"  Generated {len(shapes)} hip cap pieces\n"
    )
    return shapes


# ============================================================================
# Valley flashing generation
# ============================================================================

def generate_valley_flashing(shared_edge, face1, face2, params):
    """
    Generate a single flat flashing strip along the valley edge.

    The strip:
      - Spans valleyFlashingWidth centered on the edge (half on each face)
      - Runs the full length of the shared edge
      - Thickness extends outward along the bisector of the two face normals
    """
    mat_thick      = params.get('materialThickness', 0.25)
    flash_width    = params.get('valleyFlashingWidth', mat_thick * 8.0)

    App.Console.PrintMessage(
        f"Valley flashing: width={flash_width:.2f}  thickness={mat_thick:.2f}\n"
    )

    # Edge geometry
    start_pt   = shared_edge.Vertexes[0].Point
    end_pt     = shared_edge.Vertexes[-1].Point
    edge_vec   = end_pt - start_pt
    edge_len   = edge_vec.Length
    edge_dir   = edge_vec * (1.0 / edge_len)

    # Face normals → bisector
    n1 = face_normal_at_center(face1)
    n2 = face_normal_at_center(face2)
    bisector_raw = n1 + n2
    bisector     = bisector_raw * (1.0 / bisector_raw.Length)

    # Width direction
    wd_raw    = edge_dir.cross(bisector)
    width_dir = wd_raw * (1.0 / wd_raw.Length)

    # Corner: centered on edge in width direction, starts at edge start
    corner = start_pt - width_dir * (flash_width / 2.0)

    # Rotation: box X → width_dir, box Y → edge_dir, box Z → bisector
    rotation = App.Rotation(make_rotation_matrix(width_dir, edge_dir, bisector))

    strip = Part.makeBox(flash_width, edge_len, mat_thick)
    strip.Placement = App.Placement(corner, rotation)

    App.Console.PrintMessage(
        f"  Generated flashing strip ({flash_width:.2f} x {edge_len:.2f} x {mat_thick:.2f} mm)\n"
    )
    return [strip]


# ============================================================================
# Main execution
# ============================================================================

if __name__ == "__main__":

    doc = App.ActiveDocument
    if not doc:
        App.Console.PrintError("ERROR: No active document\n")
    else:
        App.Console.PrintMessage(f"\n{'='*60}\n")
        App.Console.PrintMessage(f"Roof Seam Generator v{VERSION}\n")
        App.Console.PrintMessage(f"{'='*60}\n\n")

        # --- Load parameters ---
        defaults = {
            'shingleWidth':       3.5,
            'shingleHeight':      2.0,
            'materialThickness':  0.25,
            'shingleExposure':    1.5,
            # hipCapWidth:        defaults to shingleWidth inside generate_hip_caps
            # valleyFlashingWidth: defaults to materialThickness * 8 inside generate_valley_flashing
        }
        sheet_params = get_params_from_spreadsheet(doc)
        params = {**defaults, **sheet_params}

        App.Console.PrintMessage("Parameters:\n")
        for k, v in sorted(params.items()):
            src = "(spreadsheet)" if k in sheet_params else "(default)"
            App.Console.PrintMessage(f"  {k}: {v} {src}\n")
        App.Console.PrintMessage("\n")

        # --- Validate exposure vs height ---
        if params.get('shingleExposure', 0) > params.get('shingleHeight', float('inf')):
            App.Console.PrintError(
                f"ERROR: shingleExposure ({params['shingleExposure']}) "
                f"cannot exceed shingleHeight ({params['shingleHeight']})\n\n"
            )

        else:
            # --- Get selected faces ---
            selection = Gui.Selection.getSelectionEx()
            selected_faces = []
            for sel in selection:
                if not sel.HasSubObjects:
                    continue
                for sub in sel.SubElementNames:
                    if sub.startswith("Face"):
                        idx  = int(sub[4:]) - 1
                        face = sel.Object.Shape.Faces[idx]
                        selected_faces.append((face, sel.Object))

            if len(selected_faces) != 2:
                App.Console.PrintError(
                    f"ERROR: Select exactly 2 adjacent roof faces (got {len(selected_faces)})\n\n"
                )
                # Dump raw selection state to help diagnose the cause
                App.Console.PrintMessage(f"Raw selection ({len(selection)} item(s)):\n")
                if not selection:
                    App.Console.PrintMessage(
                        "  (empty — selection was cleared before macro ran;\n"
                        "   run via toolbar button, not the Macros… dialog)\n"
                    )
                for sel in selection:
                    App.Console.PrintMessage(
                        f"  obj={sel.Object.Name}  HasSubObjects={sel.HasSubObjects}"
                        f"  SubElementNames={sel.SubElementNames}\n"
                    )
                App.Console.PrintMessage("\nUsage:\n")
                App.Console.PrintMessage("  1. Ctrl+click two adjacent roof faces in the 3D view\n")
                App.Console.PrintMessage("  2. Run via toolbar button (not Macros… dialog)\n\n")

            else:
                face1, obj1 = selected_faces[0]
                face2, obj2 = selected_faces[1]

                # --- Find shared edge (with automatic ShingledRoof unwrapping) ---
                App.Console.PrintMessage("Finding shared edge...\n")
                shared_edge, face1, obj1, face2, obj2 = resolve_shared_edge(
                    face1, obj1, face2, obj2
                )

                if shared_edge is None:
                    App.Console.PrintError(
                        "ERROR: No shared edge found between the two selected faces"
                        " (or their BaseObjects).\n"
                        "Make sure you select two adjacent roof faces that share an edge.\n\n"
                    )

                else:
                    App.Console.PrintMessage(f"  Found shared edge, length = {shared_edge.Length:.2f} mm\n")

                    # --- Classify seam type ---
                    seam_type = classify_seam(face1, face2, shared_edge)
                    App.Console.PrintMessage(f"  Seam type: {seam_type.upper()}\n\n")

                    # --- Generate geometry ---
                    base_name = obj1.Name

                    if seam_type == 'hip':
                        shapes = generate_hip_caps(shared_edge, face1, face2, params)
                        output_name = f"HipCap_{base_name}"
                    else:
                        shapes = generate_valley_flashing(shared_edge, face1, face2, params)
                        output_name = f"ValleyFlashing_{base_name}"

                    if not shapes:
                        App.Console.PrintError("ERROR: No geometry generated.\n")

                    else:
                        # --- Create output Part::Feature (undoable) ---
                        compound = Part.Compound(shapes)
                        commit_result(
                            doc, output_name, compound,
                            GENERATOR_NAME, VERSION,
                            extra_props={
                                "SeamType": ("App::PropertyString", "Metadata",
                                             "Seam type (hip or valley)", seam_type),
                            },
                        )

                        App.Console.PrintMessage(f"\n{'='*60}\n")
                        App.Console.PrintMessage(f"SUCCESS: Created '{output_name}' ({len(shapes)} piece(s))\n")
                        App.Console.PrintMessage(f"{'='*60}\n\n")

"""
Parametric Brick Generator Macro v5.3.0

Simplified UI layer that orchestrates brick generation using brick_geometry library.
Handles FreeCAD coordinate systems and directly modifies the source wall body.

Two-step engraving approach:
  1. SHAVE: Selected faces are recessed inward by skin_depth (material_thickness).
  2. ENGRAVE: Brick-shaped pockets are cut into the recessed face by mortar_depth,
     leaving thin ridges (mortar lines) at the recessed surface.

Benefits over the old outward-extrusion approach:
  - No boundary trimming needed (pockets beyond the wall cut nothing)
  - No opening punchout needed (wall has no material at windows/doors)
  - Corners fit properly (no protruding brick surfaces)
  - Net wall thickness unchanged after bricking
  - Modifies the wall body in-place (no separate brick compound)

Supports both vertical wall faces and horizontal surfaces (ledges, caps, sills).

Version History:
- 5.3.0 (2026-03-13): ADD: Transaction wrapping for all document mutations — all brick
                           engraving operations are now a single Ctrl+Z undo step.
                           Parametric conversion, face engraving, and sketch-based output
                           each wrapped in openTransaction/commitTransaction/abortTransaction.
- 5.2.0 (2026-03-13): FIX: U snap removed from snap_origin_to_global_grid — only V (course
                           height) is snapped. U snapping shifted the origin outside the face
                           boundary, making Flemish/English C0 closers entirely invisible on
                           even courses and creating a staircase at wall edges.
                      FIX: Bricks clipped to face_slab before mortar_grid computation — bricks
                           straddling window/opening edges are now trimmed at the face boundary,
                           eliminating alternating blank strips (staircase) at window edges.
- 5.1.0 (2026-03-04): FIX: All output now goes to FreeCAD Report View (was print-only)
                      FIX: Improved face re-identification after recess boolean
                           Uses weighted scoring (normal + area + centroid) to prevent
                           mis-mapping when faces share similar properties
                      FIX: Parametric object conversion preserves sub-element selection
- 5.0.0 (2026-03-03): CHANGE: Engraved mortar approach replaces outward extrusion
                      Bricks are now cut INTO the wall as shallow pockets
                      REMOVED: Boundary trimming, opening punchout (not needed)
                      REMOVED: Separate BrickedWall compound (wall is modified in-place)
                      ADD: mortar_depth parameter (mortarDepth spreadsheet alias)
- 4.5.0 (2026-03-03): ADD: Face recess — cuts skin_depth from wall before bricking
                      so brick surfaces are flush with original wall plane
                      FIX: Corners now fit properly (no protruding brick surfaces)
                      FIX: Net wall thickness unchanged after bricking
- 4.4.0 (2026-03-03): ADD: Horizontal face support (ledges, caps, sills)
                      FIX: get_face_coordinate_system now establishes U/V in
                           horizontal plane for faces with no Z extent
                      CHANGE: brick_height/brick_depth swapped for horizontal faces
                      CHANGE: get_face_coordinate_system returns 7-tuple (is_horizontal)
- 4.3.0 (2026-03-03): FIX: Objects inside Part containers now brick at correct world position
                      REFACTOR: Global placement logic moved to shared freecad_utils library
- 4.2.0 (2024-12-02): ADD: Global 3D grid snapping for course alignment
                      FIX: Brick courses now align across all coplanar faces
                      FIX: Eliminates visible seams at face boundaries
                      IMPROVEMENT: Snaps origin to global X/Y/Z grid based on brick+mortar dimensions
- 4.1.0 (2024-12-02): ADD: Multi-face selection support (Ctrl+click faces)
                      ADD: Single compound output from multiple selected faces
                      ADD: Boundary trimming to prevent brick overflow
                      FIX: Opening detection using face.Wires instead of face.Holes
- 4.0.0 (2024-12-02): ADD: Automatic opening detection from face holes
                      ADD: Automatic punchout generation and boolean cut
                      CHANGE: Single output object with holes already punched
                      FEATURE: Works seamlessly with arrayed walls containing holes
- 3.1.0 (2024-12-02): ADD: Bay boundary detection for fused arrays
                      CHANGE: Segments brick generation at detected boundaries
                      COMPATIBLE: Works with both continuous walls and segmented bays
- 3.0.0 (2025-11-26): Initial release with bond patterns

Version: 5.3.0
Date: 2026-03-13
"""

import FreeCAD as App
import Part
import math
import sys
import os

VERSION = "5.3.0"
GENERATOR_NAME = "brick_generator"


def log(msg=""):
    """Log to FreeCAD Report View AND stdout."""
    text = str(msg)
    App.Console.PrintMessage(text + "\n")


# Try to import the geometry library
# Force fresh import every time to pick up code changes
import importlib

# Remove any cached brick_geometry module to force fresh load
if 'brick_geometry' in sys.modules:
    del sys.modules['brick_geometry']

# Add macro directory to path if needed
macro_dir = os.path.dirname(__file__)
if macro_dir not in sys.path:
    sys.path.insert(0, macro_dir)

# Also check _lib subdirectory
lib_dir = os.path.join(macro_dir, '_lib')
if lib_dir not in sys.path:
    sys.path.insert(0, lib_dir)

try:
    import brick_geometry
    from brick_geometry import BrickGeometry
    log(f"Loaded brick_geometry v{getattr(brick_geometry, '__version__', 'unknown')} from {brick_geometry.__file__}")
except ImportError as e:
    log(f"ERROR: Could not import brick_geometry module: {e}")
    log(f"Looked in: {macro_dir}")
    log(f"Looked in: {lib_dir}")
    log("Make sure brick_geometry.py is in _lib/ subdirectory or same directory as macro")
    sys.exit(1)

# Import shared FreeCAD utilities (global placement, etc.)
if 'freecad_utils' in sys.modules:
    del sys.modules['freecad_utils']
try:
    import freecad_utils
    from freecad_utils import get_global_face, log_global_placement, commit_result
    log(f"Loaded freecad_utils v{getattr(freecad_utils, '__version__', 'unknown')}")
except ImportError:
    # Fallback: define inline so macro still works if shared lib not installed yet
    log("WARNING: freecad_utils not found in _lib/ — using inline fallback")
    def get_global_face(obj, face_index):
        face = obj.Shape.Faces[face_index]
        try:
            placement = obj.getGlobalPlacement()
            if not placement.isIdentity():
                face = face.transformShape(placement.toMatrix())
        except AttributeError:
            pass
        return face
    def log_global_placement(obj, label=None):
        pass
    def commit_result(doc, object_name, shape, generator_name, generator_version,
                      extra_props=None, transaction_label=None):
        """Inline fallback: create output object without transaction wrapping."""
        import Part
        label = transaction_label or f"{generator_name}: {object_name}"
        doc.openTransaction(label)
        try:
            result = doc.addObject("Part::Feature", object_name)
            result.Shape = shape
            result.addProperty("App::PropertyString", "GeneratorName", "Metadata", "Generator name")
            result.GeneratorName = generator_name
            result.addProperty("App::PropertyString", "GeneratorVersion", "Metadata", "Generator version")
            result.GeneratorVersion = generator_version
            if extra_props:
                for prop_name, (prop_type, group, tooltip, value) in extra_props.items():
                    result.addProperty(prop_type, prop_name, group, tooltip)
                    setattr(result, prop_name, value)
            doc.recompute()
            doc.commitTransaction()
        except Exception:
            doc.abortTransaction()
            raise
        return result


def recess_faces(sel_obj, sub_elements, skin_depth):
    """
    Recess selected faces inward by skin_depth so bricks end up flush with the
    original wall surface instead of protruding outward.

    For each face:
      1. Duplicate using OuterWire only (fills openings)
      2. Extrude inward along -normal by skin_depth
      3. Boolean cut from the source body

    All faces are compounded into a single cut to minimize boolean operations.

    After the cut, face indices shift. This function re-identifies each
    original face in the new topology by matching normal direction and
    centroid proximity, returning an updated sub_elements list.

    Args:
        sel_obj: The selected FreeCAD object whose shape will be modified
        sub_elements: List of face sub-element names (e.g. ['Face1', 'Face3'])
        skin_depth: Depth to recess (mm), typically material_thickness

    Returns:
        list: Updated sub_element names mapping to the recessed faces,
              or None if recess failed
    """
    recess_solids = []

    # Record each face's identity before the cut so we can re-find them after
    face_signatures = []  # (sub_element, normal, centroid, area)
    for sub_element in sub_elements:
        face_index = int(sub_element.replace('Face', '')) - 1
        face = get_global_face(sel_obj, face_index)

        normal = face.normalAt(0, 0)
        centroid = face.CenterOfMass
        area = face.Area
        face_signatures.append((sub_element, normal, centroid, area))

        # Create solid face from outer wire only (fills window/door openings)
        outer_wire = face.OuterWire
        solid_face = Part.Face(outer_wire)

        # Extrude inward (opposite to normal) by skin_depth
        inward_vec = scale_vector(normal, -skin_depth)
        recess_solid = solid_face.extrude(inward_vec)

        recess_solids.append(recess_solid)

    if not recess_solids:
        return None

    # Compound all recess volumes and cut from body in one operation
    if len(recess_solids) == 1:
        recess_shape = recess_solids[0]
    else:
        # Fuse all recess volumes so we do a single boolean cut
        recess_shape = recess_solids[0]
        for solid in recess_solids[1:]:
            recess_shape = recess_shape.fuse(solid)

    try:
        new_shape = sel_obj.Shape.cut(recess_shape)
        if new_shape.isNull():
            log("  WARNING: Recess cut returned null shape, skipping recess")
            return None
        sel_obj.Shape = new_shape
    except Exception as e:
        log(f"  WARNING: Recess cut failed: {e}")
        return None

    # Re-identify faces after the boolean changed topology.
    # The recessed face has the same normal as the original but its centroid
    # shifted inward by skin_depth along -normal.
    #
    # Uses a scoring system with greedy assignment to prevent two original
    # faces from mapping to the same new face (which would cause one face
    # to be silently skipped).
    claimed_indices = set()  # Prevent duplicate assignments
    new_sub_elements = []

    for orig_name, orig_normal, orig_centroid, orig_area in face_signatures:
        # Expected centroid of the recessed face
        expected_centroid = orig_centroid + scale_vector(orig_normal, -skin_depth)

        candidates = []
        for i, new_face in enumerate(sel_obj.Shape.Faces):
            if i in claimed_indices:
                continue  # Already assigned to another original face
            new_normal = new_face.normalAt(0, 0)
            # Normal must match direction (dot product ~1.0)
            dot = orig_normal.dot(new_normal)
            if dot < 0.99:
                continue
            # Area must be similar (within 10%)
            area_ratio = abs(new_face.Area - orig_area) / max(orig_area, 0.001)
            if area_ratio > 0.10:
                continue
            # Centroid distance to expected position
            dist = expected_centroid.distanceToPoint(new_face.CenterOfMass)
            # Score: lower is better. Weight centroid distance heavily,
            # add small penalty for area mismatch
            score = dist + area_ratio * 10.0
            candidates.append((score, dist, area_ratio, i))

        if candidates:
            candidates.sort()  # Best score first
            score, dist, area_ratio, best_idx = candidates[0]
            claimed_indices.add(best_idx)
            new_name = f"Face{best_idx + 1}"
            log(f"  Face remapped: {orig_name} -> {new_name} "
                f"(dist={dist:.4f}mm, area_diff={area_ratio:.4f}, "
                f"candidates={len(candidates)})")
            new_sub_elements.append(new_name)
        else:
            log(f"  WARNING: Could not re-identify {orig_name} after recess, keeping original")
            new_sub_elements.append(orig_name)

    return new_sub_elements


def detect_openings_and_create_punchout(face, origin, u_vec, v_vec, normal, brick_depth):
    """
    Detect openings (holes) in the face and create punchout geometry.
    
    Openings are detected by checking for inner wires in the face.
    A face with holes has an OuterWire (boundary) plus inner wires (holes).
    Each hole is extruded perpendicular to the wall to create a punchout shape
    that can be boolean cut from bricks.
    
    Args:
        face: The wall face to analyze
        origin: Wall origin point
        u_vec: Horizontal direction vector
        v_vec: Vertical direction vector
        normal: Wall normal (perpendicular direction)
        brick_depth: Depth to extrude punchouts
        
    Returns:
        Part.Shape: Compound of punchout shapes, or None if no holes
    """
    # In FreeCAD, face.Wires contains all wires - OuterWire plus any holes
    # If there's only one wire, there are no holes
    all_wires = face.Wires
    if len(all_wires) <= 1:
        log("  No openings detected")
        return None
    
    # Filter out the outer wire - it's the one with the largest area
    # This is more reliable than direct comparison
    outer_wire = face.OuterWire
    
    # Alternative: find largest wire by length (outer boundary is longest)
    wire_lengths = [(w, w.Length) for w in all_wires]
    wire_lengths.sort(key=lambda x: x[1], reverse=True)
    largest_wire = wire_lengths[0][0]
    
    # Get inner wires (holes) - everything except the largest
    hole_wires = [w for w, length in wire_lengths[1:]]
    
    if not hole_wires:
        log("  No openings detected")
        return None
    
    log(f"  Found {len(hole_wires)} opening(s) - creating punchout geometry...")
    log(f"  DEBUG: Total wires={len(all_wires)}, holes={len(hole_wires)}")
    punchout_shapes = []
    
    # Use generous 10mm extrusion depth (doesn't need to be precise)
    punchout_depth = 10.0  # mm
    
    try:
        for hole_idx, hole_wire in enumerate(hole_wires):
            try:
                # Create a face from the hole wire
                hole_face = Part.Face(hole_wire)
                
                # Debug: show hole face area
                area = hole_face.Area
                bbox = hole_face.BoundBox
                log(f"    Opening {hole_idx + 1}: area={area:.2f}mm², size={bbox.XLength:.1f}x{bbox.YLength:.1f}x{bbox.ZLength:.1f}mm")
                
                # Extrude generously in both directions (10mm each way = 20mm total)
                # This ensures we punch through regardless of exact brick positioning
                extrude_vec = scale_vector(normal, punchout_depth * 2)
                start_offset = scale_vector(normal, -punchout_depth)
                hole_face_translated = hole_face.translated(start_offset)
                
                # Create the punchout by extruding
                punchout = hole_face_translated.extrude(extrude_vec)
                punchout_shapes.append(punchout)
                log(f"    Opening {hole_idx + 1}: punchout created (extruded {punchout_depth*2:.1f}mm total)")
            except Exception as e:
                log(f"    Opening {hole_idx + 1}: WARNING - Could not create punchout: {e}")
                continue
        
        # Create compound of all punchouts
        if punchout_shapes:
            if len(punchout_shapes) == 1:
                punchout_compound = punchout_shapes[0]
            else:
                punchout_compound = Part.Compound(punchout_shapes)
            log(f"  ✓ Punchout geometry ready ({len(punchout_shapes)} opening(s))")
            return punchout_compound
            
    except Exception as e:
        log(f"  WARNING: Could not create punchout geometry: {e}")
        log(f"  Continuing with bricks only (no holes)")
        return None
    
    return None


def snap_origin_to_global_grid(origin, u_vec, v_vec, brick_width, brick_height, mortar):
    """
    Snap face origin to global 3D grid to align brick courses across all faces.

    This ensures that brick courses and columns align perfectly across coplanar faces,
    eliminating visible seams at face boundaries.

    IMPORTANT: Only snaps along the wall plane (u and v directions), NOT along the
    normal direction. This preserves the origin's position on the wall surface.

    Args:
        origin: Face origin point (FreeCAD.Vector)
        u_vec: Horizontal direction vector (normalized)
        v_vec: Vertical direction vector (normalized)
        brick_width: Brick width in mm
        brick_height: Brick height in mm
        mortar: Mortar thickness in mm

    Returns:
        Snapped origin point (FreeCAD.Vector)
    """
    # Grid spacings
    horizontal_grid = brick_width + mortar  # e.g., 2.43mm for stretcher bond
    vertical_grid = brick_height + mortar    # e.g., 0.76mm

    # Calculate normal as cross product of u and v
    normal = u_vec.cross(v_vec)
    normal.normalize()

    # Project origin onto wall-aligned axes
    origin_u = origin.dot(u_vec)  # Position along horizontal wall direction
    origin_v = origin.dot(v_vec)  # Position along vertical wall direction
    origin_n = origin.dot(normal) # Position along normal (preserve this!)

    # Snap only V (vertical) to grid — aligns horizontal mortar courses across faces.
    # U (horizontal) is NOT snapped: bond types with closers (Flemish, English, Common)
    # compute closers to exactly fill the face width, and snapping U would shift the
    # origin outside the face boundary, making closers partly or fully invisible and
    # creating a staircase pattern at wall edges.
    snapped_u = origin_u  # No horizontal snap
    snapped_v = round(origin_v / vertical_grid) * vertical_grid

    # Reconstruct snapped origin
    snapped_origin = (scale_vector(u_vec, snapped_u) +
                      scale_vector(v_vec, snapped_v) +
                      scale_vector(normal, origin_n))

    # Calculate adjustment (only in wall plane)
    adjustment_u = snapped_u - origin_u
    adjustment_v = snapped_v - origin_v
    adjustment_distance = math.sqrt(adjustment_u**2 + adjustment_v**2)

    if adjustment_distance > 0.001:  # Only report if meaningful adjustment
        log(f"  Grid snapping: adjusted origin by {adjustment_distance:.3f}mm (in wall plane)")
        log(f"    U (horizontal): {origin_u:.3f} → {snapped_u:.3f} mm (not snapped)")
        log(f"    V (vertical): {origin_v:.3f} → {snapped_v:.3f} mm")
        log(f"    Normal: {origin_n:.3f} mm (unchanged)")

    return snapped_origin


def find_bay_boundaries(outer_wire, u_vec, v_vec, gap_threshold=0.0005, max_gap=0.02):
    """
    Find vertical gaps in the outer wire that represent bay boundaries.

    This detects discontinuities in the wall face where bays are separated
    by small gaps (typically fudgeFactor-sized, ~0.001mm) after fusing arrays.

    Args:
        outer_wire: Face outer wire to analyze
        u_vec: Horizontal axis direction vector
        v_vec: Vertical axis direction vector
        gap_threshold: Minimum gap size to consider a boundary (mm)
        max_gap: Maximum gap size to consider a boundary (mm).
                 Fuse artifacts are ~0.001mm; mortar groove artifacts
                 are 0.06mm+.  Keep below mortar_depth to avoid false
                 bay boundaries when re-running on already-bricked objects.

    Returns:
        List of positions along u_vec where boundaries are detected
    """
    # Determine which FreeCAD axis corresponds to our vertical direction
    # v_vec should have Z component (vertical in FreeCAD)
    angle_tolerance = 5.0  # degrees
    
    # Get all edges from the wire
    vertical_edges = []
    
    for edge in outer_wire.Edges:
        if edge.Length < 0.01:
            continue
        
        try:
            direction = edge.tangentAt(edge.FirstParameter)
            direction.normalize()
            
            # Check if edge is parallel to v_vec (vertical)
            dot_product = abs(direction.dot(v_vec))
            angle = math.degrees(math.acos(min(1.0, dot_product)))
            
            # This is a vertical edge
            if angle < angle_tolerance:
                start = edge.valueAt(edge.FirstParameter)
                end = edge.valueAt(edge.LastParameter)
                
                # Get position along u_vec (horizontal position)
                u_pos = start.dot(u_vec)
                
                vertical_edges.append({
                    'u_pos': u_pos,
                    'edge': edge,
                    'start': start,
                    'end': end
                })
        except Exception as e:
            continue
    
    if len(vertical_edges) < 2:
        return []
    
    # Sort by horizontal position
    vertical_edges.sort(key=lambda e: e['u_pos'])
    
    # Find gaps between adjacent vertical edges
    bay_boundaries = []
    
    for i in range(len(vertical_edges) - 1):
        u1 = vertical_edges[i]['u_pos']
        u2 = vertical_edges[i + 1]['u_pos']
        gap = u2 - u1
        
        # If gap is within the bay-boundary range, this is a fuse artifact
        if gap > gap_threshold and gap < max_gap:
            # Store the midpoint of the gap as the boundary
            boundary_pos = (u1 + u2) / 2
            bay_boundaries.append(boundary_pos)
            log(f"  Found bay boundary at u={boundary_pos:.3f} (gap={gap:.4f}mm)")
    
    return bay_boundaries


def create_brick_segments(u_length, bay_boundaries):
    """
    Create segments from bay boundaries.
    
    Args:
        u_length: Total wall width
        bay_boundaries: List of boundary positions
        
    Returns:
        List of (start, end, width) tuples for each segment
    """
    segments = []
    prev_boundary = 0.0
    
    for boundary in sorted(bay_boundaries):
        if boundary > prev_boundary + 0.001:  # Skip tiny segments
            width = boundary - prev_boundary
            segments.append((prev_boundary, boundary, width))
        prev_boundary = boundary
    
    # Add final segment
    if prev_boundary < u_length - 0.001:
        width = u_length - prev_boundary
        segments.append((prev_boundary, u_length, width))
    
    # If no valid segments, use full width
    if len(segments) == 0:
        segments = [(0.0, u_length, u_length)]
    
    return segments


def generate_segmented_bricks(u_length, v_length, brick_width, brick_height, brick_depth,
                              mortar, bond_type, common_bond_count, bay_boundaries,
                              skin_depth=None):
    """
    Generate bricks with optional bay segmentation.

    Args:
        skin_depth: Rendered brick depth (defaults to brick_depth if not specified)

    Returns:
        Tuple of (brick_defs, metadata)
    """
    # Create segments if boundaries exist
    segments = create_brick_segments(u_length, bay_boundaries)
    log(f"Generating {len(segments)} segment(s)")

    all_brick_defs = []
    total_metadata = {'num_courses': 0, 'bond_type': bond_type}

    for seg_idx, (seg_start, seg_end, seg_width) in enumerate(segments):
        if len(segments) > 1:
            log(f"  Segment {seg_idx + 1}: u={seg_start:.1f} to {seg_end:.1f} (width={seg_width:.1f}mm)")

        bg = BrickGeometry(
            u_length=seg_width,
            v_length=v_length,
            brick_width=brick_width,
            brick_height=brick_height,
            brick_depth=brick_depth,
            mortar=mortar,
            bond_type=bond_type,
            common_bond_count=common_bond_count,
            skin_depth=skin_depth
        )
        
        result = bg.generate()
        brick_defs = result['bricks']
        metadata = result['metadata']
        
        # Offset brick positions by segment start
        for brick_def in brick_defs:
            # Create new BrickDef with offset u position
            from brick_geometry import BrickDef
            offset_brick = BrickDef(
                index=len(all_brick_defs),
                u=brick_def.u + seg_start,
                v=brick_def.v,
                course=brick_def.course,
                brick_type=brick_def.brick_type,
                width=brick_def.width,
                height=brick_def.height,
                depth=brick_def.depth
            )
            all_brick_defs.append(offset_brick)
        
        total_metadata['num_courses'] = max(total_metadata['num_courses'], 
                                            metadata['num_courses'])
    
    return all_brick_defs, total_metadata


def get_face_coordinate_system(face):
    """
    Establish a coordinate system for the face using bounding box analysis.

    Returns:
        tuple: (origin, u_vec, v_vec, normal, u_length, v_length, is_horizontal)

    Coordinate system for vertical faces:
    - u_vec: largest non-Z horizontal extent (left-right along wall)
    - v_vec: Z axis (up)
    - normal: perpendicular to wall (outward)

    Coordinate system for horizontal faces (no Z extent, e.g. ledges/caps):
    - u_vec: largest horizontal extent (brick length direction)
    - v_vec: other horizontal axis (brick depth = 3.75" becomes V row pitch)
    - normal: ±Z (outward from face)
    - Caller must swap brick_height/brick_depth parameters for correct sizing.

    is_horizontal: True if the face has no meaningful Z extent.
    """
    
    outer_wire = face.OuterWire
    bbox = outer_wire.BoundBox
    
    # Origin at lowest corner
    origin = App.Vector(bbox.XMin, bbox.YMin, bbox.ZMin)
    
    # Get all vertices to analyze axis ranges
    vertices = outer_wire.Vertexes
    points = [v.Point for v in vertices]
    
    x_vals = [p.x for p in points]
    y_vals = [p.y for p in points]
    z_vals = [p.z for p in points]
    
    x_min, x_max = min(x_vals), max(x_vals)
    y_min, y_max = min(y_vals), max(y_vals)
    z_min, z_max = min(z_vals), max(z_vals)
    
    x_range = x_max - x_min
    y_range = y_max - y_min
    z_range = z_max - z_min
    
    # Identify the three axes by their ranges
    axes = [
        (x_range, 'x', App.Vector(1, 0, 0)),
        (y_range, 'y', App.Vector(0, 1, 0)),
        (z_range, 'z', App.Vector(0, 0, 1))
    ]
    axes.sort(reverse=True)  # Sort by range, largest first
    
    # The vertical axis should have Z component (be the Z-axis or one of the others)
    # Strategy: one of u/v should be Z, the other should be X or Y
    
    # Find which is the Z axis
    z_axis = None
    other_axes = []
    for rng, name, vec in axes:
        if name == 'z':
            z_axis = (rng, name, vec)
        else:
            other_axes.append((rng, name, vec))
    
    # Get face normal first - we need this to determine which axes are on the face
    u_range = face.ParameterRange[:2]
    v_range = face.ParameterRange[2:]
    u_mid = (u_range[0] + u_range[1]) / 2
    v_mid = (v_range[0] + v_range[1]) / 2
    normal = face.normalAt(u_mid, v_mid)

    # v_vec should be the Z axis (vertical)
    # u_vec should be the largest non-Z axis that is TANGENT to the face (perpendicular to normal)
    if z_axis and z_axis[0] > 0.001:  # Has meaningful Z extent — vertical face
        v_vec = z_axis[2]
        v_length = z_axis[0]

        # u_vec is the largest non-Z axis that's tangent to the face
        # Check each candidate axis - pick the one most perpendicular to normal
        best_u_vec = None
        best_u_length = 0
        for rng, name, vec in other_axes:
            dot = abs(vec.dot(normal))
            # If dot product is small, this axis is tangent to the face
            if dot < 0.5:  # More perpendicular to normal than parallel
                if rng > best_u_length:
                    best_u_vec = vec
                    best_u_length = rng

        if best_u_vec is None:
            # Fallback: use the largest non-Z axis anyway
            best_u_vec = other_axes[0][2]
            best_u_length = other_axes[0][0]
            log(f"  WARNING: Could not find axis tangent to face, using {other_axes[0][1]}")

        u_vec = best_u_vec
        u_length = best_u_length
        is_horizontal = False

    else:
        # Horizontal face: normal is approximately ±Z (ledge, cap, sill, etc.)
        # Establish U and V axes entirely in the horizontal plane.
        #
        # Brick dimension remapping (handled by caller):
        #   V row pitch    = brick_depth  (3.75" — the 3D brick depth becomes the row width)
        #   Extrusion depth = brick_height (2.25" — the brick height goes into the surface)
        #
        # U = largest horizontal extent (bricks run their 8" dimension along this axis)
        # V = other horizontal axis    (3.75" per course)
        horiz = [(rng, name, vec) for rng, name, vec in axes if name != 'z']
        horiz.sort(reverse=True)  # Largest extent first

        if len(horiz) < 2 or horiz[0][0] < 0.001:
            raise ValueError("Selected face has no meaningful horizontal extent.")

        u_vec = horiz[0][2]
        u_length = horiz[0][0]
        v_vec = horiz[1][2]
        v_length = horiz[1][0] if horiz[1][0] > 0.001 else u_length
        is_horizontal = True

        log(f"  Horizontal face detected: "
              f"U={horiz[0][1]}-axis ({u_length:.1f}mm), "
              f"V={horiz[1][1]}-axis ({v_length:.1f}mm)")

    return origin, u_vec, v_vec, normal, u_length, v_length, is_horizontal


def scale_vector(vec, scale):
    """Helper to scale a vector."""
    return App.Vector(vec.x * scale, vec.y * scale, vec.z * scale)


def create_brick_from_def(brick_def, origin, u_vec, v_vec, normal):
    """
    Create a FreeCAD brick solid from a brick definition.
    
    Constructs brick by building vertices in world space using wall coordinate vectors.
    This ensures correct positioning and orientation without matrix transformations.
    
    Args:
        brick_def: BrickDef with position, dimensions, and type
        origin: Wall origin point
        u_vec: Horizontal direction (left-right on wall, normalized)
        v_vec: Vertical direction (up-down on wall, normalized)
        normal: Wall normal (perpendicular out, normalized)
        
    Returns:
        Part.Shape: Brick solid
    """
    
    # Brick dimensions and position
    u_pos = brick_def.u
    v_pos = brick_def.v
    width = brick_def.width
    height = brick_def.height
    depth = brick_def.depth
    
    # Build 8 vertices in world space
    # Each vertex = origin + u_offset*u_vec + v_offset*v_vec + n_offset*normal
    
    # Near face — sits on the wall surface (recessed face after shave)
    p0 = origin + scale_vector(u_vec, u_pos) + scale_vector(v_vec, v_pos)
    p1 = origin + scale_vector(u_vec, u_pos + width) + scale_vector(v_vec, v_pos)
    p2 = origin + scale_vector(u_vec, u_pos + width) + scale_vector(v_vec, v_pos + height)
    p3 = origin + scale_vector(u_vec, u_pos) + scale_vector(v_vec, v_pos + height)

    # Far face — extrudes INWARD (into wall) by depth
    p4 = p0 + scale_vector(normal, -depth)
    p5 = p1 + scale_vector(normal, -depth)
    p6 = p2 + scale_vector(normal, -depth)
    p7 = p3 + scale_vector(normal, -depth)
    
    # Create the 12 edges
    e0 = Part.Edge(Part.LineSegment(p0, p1).toShape())
    e1 = Part.Edge(Part.LineSegment(p1, p2).toShape())
    e2 = Part.Edge(Part.LineSegment(p2, p3).toShape())
    e3 = Part.Edge(Part.LineSegment(p3, p0).toShape())
    
    e4 = Part.Edge(Part.LineSegment(p4, p5).toShape())
    e5 = Part.Edge(Part.LineSegment(p5, p6).toShape())
    e6 = Part.Edge(Part.LineSegment(p6, p7).toShape())
    e7 = Part.Edge(Part.LineSegment(p7, p4).toShape())
    
    e8 = Part.Edge(Part.LineSegment(p0, p4).toShape())
    e9 = Part.Edge(Part.LineSegment(p1, p5).toShape())
    e10 = Part.Edge(Part.LineSegment(p2, p6).toShape())
    e11 = Part.Edge(Part.LineSegment(p3, p7).toShape())
    
    # Create the 6 faces
    wire_near = Part.Wire([e0, e1, e2, e3])
    wire_far = Part.Wire([e4, e5, e6, e7])
    wire_bottom = Part.Wire([e0, e9, e4, e8])
    wire_top = Part.Wire([e2, e10, e6, e11])
    wire_left = Part.Wire([e3, e8, e7, e11])
    wire_right = Part.Wire([e1, e9, e5, e10])
    
    face_near = Part.Face(wire_near)
    face_far = Part.Face(wire_far)
    face_bottom = Part.Face(wire_bottom)
    face_top = Part.Face(wire_top)
    face_left = Part.Face(wire_left)
    face_right = Part.Face(wire_right)
    
    # Create shell and solid
    shell = Part.Shell([face_near, face_far, face_bottom, face_top, face_left, face_right])
    brick = Part.Solid(shell)
    
    return brick


def get_params_from_spreadsheet(doc):
    """Try to read parameters from spreadsheet. Returns dict of found params (may be partial)."""
    params = {}

    try:
        ss = doc.getObject("Spreadsheet")
        if ss is None:
            log("WARNING: No 'Spreadsheet' object found in document — all brick params will use defaults")
            return params

        param_map = {
            'brick_width':        'brickWidth',
            'brick_height':       'brickHeight',
            'brick_depth':        'brickDepth',
            'mortar':             'mortar',
            'bond_type':          'bondType',
            'common_bond_count':  'commonBondCount',
            'material_thickness': 'materialThickness',
        }

        for param_key, alias in param_map.items():
            try:
                val = ss.get(alias)
                if val is not None:
                    params[param_key] = str(val) if param_key == 'bond_type' else float(val)
            except:
                pass  # alias not in spreadsheet — will be caught by resolve_brick_params

    except Exception as e:
        log(f"WARNING: Error reading spreadsheet: {e}")

    return params


# Defaults and descriptions used by resolve_brick_params
_BRICK_PARAM_DEFAULTS = {
    'brick_width':        (2.32,        'brickWidth',       'mm  (HO 8" stretcher)'),
    'brick_height':       (0.65,        'brickHeight',      'mm  (HO 2.25")'),
    'brick_depth':        (1.09,        'brickDepth',       'mm  (HO 3.75")'),
    'mortar':             (0.11,        'mortar',           'mm  (HO ~0.375" joint)'),
    'bond_type':          ('stretcher', 'bondType',         'stretcher/english/flemish/common'),
    'common_bond_count':  (5,           'commonBondCount',  'header courses for common bond'),
    'material_thickness': (0.3,         'materialThickness','mm  rendered skin depth'),
    'mortar_depth':       (0.06,        'mortarDepth',      'mm  mortar groove depth (engraved)'),
}


def resolve_brick_params(params):
    """
    Resolve final brick params from spreadsheet dict, warning loudly for each
    missing entry so the user knows exactly why defaults are being applied.

    Returns dict with keys: brick_width, brick_height, brick_depth, mortar,
                            bond_type, common_bond_count, material_thickness
    """
    resolved = {}
    missing = []

    for key, (default, alias, desc) in _BRICK_PARAM_DEFAULTS.items():
        if key in params:
            resolved[key] = params[key]
        else:
            resolved[key] = default
            missing.append((alias, default, desc))

    if missing:
        log(f"\n{'!'*60}")
        log(f"! BRICK GENERATOR — {len(missing)} param(s) not found in spreadsheet:")
        for alias, default, desc in missing:
            log(f"!   {alias:22s} → using default {default!r}  ({desc})")
        log(f"! Add these aliases to your spreadsheet to control them.")
        log(f"{'!'*60}\n")
    else:
        log("✓ All brick params loaded from spreadsheet")

    return resolved


# ============================================================================
# MACRO EXECUTION
# ============================================================================

if __name__ == '__main__' or __name__ == '__console__' or __name__ == '__plugins__':
    doc = App.ActiveDocument
    
    if doc is None:
        log("ERROR: No active document. Please create or open a document first.")
    else:
        # Get selection
        selection = App.Gui.Selection.getSelectionEx()
        
        if not selection:
            log("ERROR: Please select a sketch or face to apply bricks to.")
        else:
            sel_obj = selection[0].Object
            obj_name = sel_obj.Label

            # Parametric objects (Part::Box, Part::Extrusion, Part::Cut, etc.)
            # recalculate their shape on recompute, overwriting any direct
            # Shape assignment.  Convert to a plain Part::Feature first so
            # the mortar engraving survives recompute.
            if sel_obj.TypeId != 'Part::Feature' and sel_obj.TypeId != 'Sketcher::SketchObject':
                if hasattr(sel_obj, 'Shape') and not sel_obj.Shape.isNull():
                    log(f"NOTE: {obj_name} is parametric ({sel_obj.TypeId})")
                    log(f"  Converting to Part::Feature so mortar engraving is preserved...")
                    doc.openTransaction(f"brick_generator: freeze {obj_name}")
                    try:
                        frozen = doc.addObject("Part::Feature", obj_name + "_Bricked")
                        frozen.Shape = sel_obj.Shape.copy()
                        # Transfer the visual appearance
                        if hasattr(sel_obj, 'ViewObject') and hasattr(frozen, 'ViewObject'):
                            try:
                                frozen.ViewObject.ShapeColor = sel_obj.ViewObject.ShapeColor
                            except Exception:
                                pass
                        # Hide the original
                        try:
                            sel_obj.ViewObject.Visibility = False
                        except Exception:
                            pass
                        doc.recompute()
                        doc.commitTransaction()
                    except Exception:
                        doc.abortTransaction()
                        raise
                    # Carry forward the original sub-element selection
                    sel_obj = frozen
                    obj_name = frozen.Label
                    log(f"  ✓ Created {obj_name} (original hidden)")

            # Determine if this is a sketch or a face selection
            is_sketch = (sel_obj.TypeId == 'Sketcher::SketchObject')
            
            if is_sketch:
                # Sketch-based workflow
                sketch = sel_obj
                
                log(f"\n{'='*60}")
                log(f"Generating bricks for sketch: {obj_name}")
                log(f"{'='*60}")
                
                try:
                    # Get sketch outer wire (assumes sketch is closed)
                    if not hasattr(sketch, 'Shape') or len(sketch.Shape.Wires) == 0:
                        raise ValueError("Sketch has no valid wires")
                    
                    outer_wire = max(sketch.Shape.Wires, key=lambda w: abs(Part.Face(w).Area))
                    face = Part.Face(outer_wire)
                    
                    # Get parameters first (needed for grid snapping)
                    params = resolve_brick_params(get_params_from_spreadsheet(doc))
                    brick_width = params['brick_width']
                    brick_height = params['brick_height']
                    brick_depth = params['brick_depth']
                    skin_depth = params['material_thickness']
                    mortar = params['mortar']
                    bond_type = params['bond_type']
                    common_bond_count = int(params['common_bond_count'])
                    
                    # Get face coordinate system
                    origin, u_vec, v_vec, normal, u_length, v_length, is_horizontal = get_face_coordinate_system(face)

                    # For horizontal faces, remap brick dimensions:
                    #   V row pitch     = brick_depth  (3.75" — face-parallel dimension)
                    #   Extrusion depth = brick_height (2.25" — into the surface)
                    gen_brick_height = brick_depth if is_horizontal else brick_height
                    gen_brick_depth  = brick_height if is_horizontal else brick_depth

                    # Snap origin to global grid for course alignment
                    origin = snap_origin_to_global_grid(origin, u_vec, v_vec, brick_width, gen_brick_height, mortar)

                    # Bricks extrude outward along the normal from the wall surface
                    # No origin offset needed - bricks start at wall surface

                    # Detect bay boundaries
                    log("Checking for bay boundaries...")
                    gap_threshold = 0.0005  # Half of typical fudgeFactor
                    bay_boundaries = find_bay_boundaries(outer_wire, u_vec, v_vec, gap_threshold)

                    if len(bay_boundaries) > 0:
                        log(f"Found {len(bay_boundaries)} bay boundaries - will create segmented bricks")
                    else:
                        log("No bay boundaries detected - creating continuous brick wall")
                    log()

                    orient = "horizontal" if is_horizontal else "vertical"
                    log(f"Face orientation: {orient}")
                    log(f"Face dimensions: {u_length:.1f} x {v_length:.1f} mm")
                    log(f"Brick (W×H×D): {brick_width} x {brick_height} x {brick_depth} mm")
                    if is_horizontal:
                        log(f"  → horizontal remapping: row pitch={gen_brick_height:.2f}mm, depth={gen_brick_depth:.2f}mm")
                    log(f"Mortar: {mortar} mm")
                    log(f"Bond: {bond_type}")
                    if bond_type.lower() == 'common':
                        log(f"Common bond count: {common_bond_count}")
                    log()

                    # Generate geometry with segmentation
                    log("Generating geometry...")
                    brick_defs, metadata = generate_segmented_bricks(
                        u_length, v_length, brick_width, gen_brick_height, gen_brick_depth,
                        mortar, bond_type, common_bond_count, bay_boundaries,
                        skin_depth=skin_depth
                    )
                    
                    log(f"Generated {len(brick_defs)} brick definitions")
                    log(f"Bond pattern: {metadata['bond_type']}")
                    log(f"Number of courses: {metadata['num_courses']}")
                    log()
                    
                    # Create FreeCAD objects
                    log("Creating FreeCAD geometry...")
                    brick_shapes = []
                    log(f"DEBUG: origin={origin}")
                    log(f"DEBUG: u_vec={u_vec} (horizontal along wall)")
                    log(f"DEBUG: v_vec={v_vec} (vertical)")
                    log(f"DEBUG: normal={normal} (perpendicular to wall)")
                    log(f"DEBUG: u_length={u_length:.2f}mm, v_length={v_length:.2f}mm")
                    log(f"DEBUG: u_vec dot normal = {u_vec.dot(normal):.4f} (should be ~0)")
                    for i, brick_def in enumerate(brick_defs):
                        brick = create_brick_from_def(brick_def, origin, u_vec, v_vec, normal)
                        brick_shapes.append(brick)
                        
                        if (i + 1) % 1000 == 0:
                            log(f"  Created {i+1}/{len(brick_defs)} bricks...")
                    
                    log(f"Creating compound of {len(brick_shapes)} bricks...")
                    result_shape = Part.Compound(brick_shapes)
                    log(f"✓ Compound created (instant, no fusing)")
                    
                    # For object-based workflow, try to detect openings from main faces
                    log("Checking for openings...")
                    punchout_shapes = []
                    try:
                        # Try to get holes from the main faces
                        for face in sel_obj.Shape.Faces:
                            if len(face.Holes) > 0:
                                punchout = detect_openings_and_create_punchout(
                                    face, origin, u_vec, v_vec, normal, brick_depth
                                )
                                if punchout:
                                    punchout_shapes.append(punchout)
                    except Exception as e:
                        log(f"  INFO: Could not detect holes from object faces: {e}")
                    log()
                    
                    # Perform boolean cut if punchouts exist
                    if punchout_shapes:
                        log("Performing boolean cut operations...")
                        try:
                            for punchout in punchout_shapes:
                                result_shape = result_shape.cut(punchout)
                            
                            if result_shape.isNull():
                                log(f"WARNING: Cut operation returned null shape")
                            else:
                                log(f"✓ Cut completed - openings punched from bricks")
                        except Exception as e:
                            log(f"WARNING: Boolean cut failed: {e}")
                            log(f"Continuing with unpunched bricks")
                    log()
                    
                    # Create result object (undoable via transaction in commit_result)
                    result_obj = commit_result(
                        doc, f"BrickedWall_{obj_name}", result_shape,
                        GENERATOR_NAME, VERSION,
                        extra_props={
                            "SourceObject": ("App::PropertyString", "Metadata",
                                             "Source object name", obj_name),
                            "BondType":     ("App::PropertyString", "Metadata",
                                             "Bond pattern used", bond_type),
                            "BrickCount":   ("App::PropertyInteger", "Metadata",
                                             "Number of bricks generated", len(brick_defs)),
                        },
                    )
                    
                    log(f"\n✓ Created: {result_obj.Label}")
                    log(f"  Brick count: {len(brick_defs)}")
                    log(f"  Bond type: {bond_type}")
                    if punchout_shapes:
                        log(f"  Openings: Punched and cut")
                    log(f"\n{'='*60}")
                    log("SUCCESS!")
                    log(f"{'='*60}")
                    
                except Exception as e:
                    log(f"\n{'='*60}")
                    log(f"ERROR: {e}")
                    log(f"{'='*60}")
                    import traceback
                    traceback.print_exc()
            
            elif selection[0].SubObjects:
                # Face-based workflow - process all selected faces
                sub_elements = selection[0].SubElementNames
                
                log(f"\n{'='*60}")
                log(f"Generating bricks for: {obj_name}")
                log(f"Selected: {len(sub_elements)} face(s)")
                log(f"{'='*60}\n")
                
                # Get parameters once for all faces
                params = resolve_brick_params(get_params_from_spreadsheet(doc))
                brick_width = params['brick_width']
                brick_height = params['brick_height']
                brick_depth = params['brick_depth']
                skin_depth = params['material_thickness']
                mortar = params['mortar']
                bond_type = params['bond_type']
                common_bond_count = int(params['common_bond_count'])
                mortar_depth = params['mortar_depth']

                # Collect all brick shapes from all faces
                all_brick_shapes = []
                total_brick_count = 0
                faces_processed = []

                # Log if object is inside a Part container with a non-identity placement
                log_global_placement(sel_obj)

                # Recess selected faces inward so bricks end up flush with original surface
                log("Recessing faces inward by {:.3f}mm...".format(skin_depth))
                new_sub_elements = recess_faces(sel_obj, sub_elements, skin_depth)
                if new_sub_elements is not None:
                    sub_elements = new_sub_elements
                    log(f"  ✓ Faces recessed by {skin_depth:.3f}mm")
                else:
                    log("  WARNING: Face recess failed, bricks will protrude outward")

                # Process each selected face — generate brick solids that
                # extrude INWARD from the recessed face by mortar_depth.
                # These are then boolean-cut from the wall body to engrave
                # mortar grooves.  No boundary trimming or punchout needed:
                # pockets beyond the wall boundary cut nothing, and openings
                # already have no material.
                for face_num, sub_element in enumerate(sub_elements, 1):
                    try:
                        face_index = int(sub_element.replace('Face', '')) - 1
                        face = get_global_face(sel_obj, face_index)

                        log(f"\n--- Processing face {face_num}/{len(sub_elements)}: {sub_element} ---")

                        # Get face coordinate system
                        origin, u_vec, v_vec, normal, u_length, v_length, is_horizontal = get_face_coordinate_system(face)

                        # For horizontal faces, remap brick dimensions:
                        #   V row pitch     = brick_depth  (3.75" — face-parallel dimension)
                        #   Extrusion depth = brick_height (2.25" — into the surface)
                        gen_brick_height = brick_depth if is_horizontal else brick_height
                        gen_brick_depth  = brick_height if is_horizontal else brick_depth

                        # Snap origin to global grid for course alignment
                        origin = snap_origin_to_global_grid(origin, u_vec, v_vec, brick_width, gen_brick_height, mortar)

                        orient = "horizontal" if is_horizontal else "vertical"
                        log(f"  Face orientation: {orient}")
                        log(f"  u_vec={u_vec}, v_vec={v_vec}, normal={normal}")
                        if is_horizontal:
                            log(f"  Horizontal remapping: row pitch={gen_brick_height:.2f}mm, depth={gen_brick_depth:.2f}mm")

                        # Detect bay boundaries
                        log("  Checking for bay boundaries...")
                        gap_threshold = 0.0005  # Half of typical fudgeFactor
                        outer_wire = face.OuterWire
                        bay_boundaries = find_bay_boundaries(outer_wire, u_vec, v_vec, gap_threshold)

                        if len(bay_boundaries) > 0:
                            log(f"  Found {len(bay_boundaries)} bay boundaries")
                        else:
                            log("  No bay boundaries detected")

                        log(f"  Dimensions: {u_length:.1f} x {v_length:.1f} mm")

                        # Generate geometry with segmentation
                        # Pass mortar_depth as skin_depth so BrickDef.depth = mortar_depth
                        brick_defs, metadata = generate_segmented_bricks(
                            u_length, v_length, brick_width, gen_brick_height, gen_brick_depth,
                            mortar, bond_type, common_bond_count, bay_boundaries,
                            skin_depth=mortar_depth
                        )

                        log(f"  Generated {len(brick_defs)} brick definitions")

                        # Create FreeCAD brick shapes (extruded inward by mortar_depth)
                        face_brick_shapes = []
                        for brick_def in brick_defs:
                            brick = create_brick_from_def(brick_def, origin, u_vec, v_vec, normal)
                            face_brick_shapes.append(brick)

                        brick_compound = Part.Compound(face_brick_shapes)

                        # Build mortar grid = face slab minus bricks.
                        # The slab covers the whole face extruded inward by mortar_depth.
                        # Subtracting brick shapes leaves only the thin mortar lines.
                        # Cutting the mortar grid from the wall gives: mortar recessed,
                        # bricks proud (the original recessed surface).
                        slab_vec = scale_vector(normal, -mortar_depth)
                        face_slab = face.extrude(slab_vec)

                        # Clip bricks to the face slab before subtracting.
                        # Without clipping, bricks that straddle window/opening edges extend
                        # into the opening area and block mortar cuts on the wall-side, creating
                        # alternating blank strips (staircase) at each vertical window edge.
                        # Intersecting with face_slab trims each brick to the actual face shape
                        # (including window holes), so all courses have consistent boundaries.
                        try:
                            clipped_bricks = brick_compound.common(face_slab)
                            mortar_grid = face_slab.cut(clipped_bricks)
                            log(f"  ✓ Mortar grid created (slab - {len(brick_defs)} clipped bricks)")
                        except Exception as clip_err:
                            log(f"  WARNING: Brick clipping failed ({clip_err}), falling back to unclipped")
                            mortar_grid = face_slab.cut(brick_compound)
                            log(f"  ✓ Mortar grid created (slab - {len(brick_defs)} bricks, unclipped)")

                        # Add to collection
                        all_brick_shapes.append(mortar_grid)
                        total_brick_count += len(brick_defs)
                        faces_processed.append(sub_element)

                        log(f"  ✓ Face {sub_element} complete ({len(brick_defs)} bricks)")

                    except Exception as e:
                        log(f"\n{'='*60}")
                        log(f"ERROR processing {sub_element}: {e}")
                        log(f"{'='*60}")
                        import traceback
                        traceback.print_exc()
                        continue

                # Engrave mortar grooves: cut mortar grids from the wall
                if all_brick_shapes:
                    log(f"\n{'='*60}")
                    log(f"Engraving mortar grooves for {total_brick_count} bricks on {len(faces_processed)} face(s)...")
                    log(f"{'='*60}")

                    try:
                        if len(all_brick_shapes) == 1:
                            mortar_compound = all_brick_shapes[0]
                        else:
                            mortar_compound = Part.Compound(all_brick_shapes)

                        new_shape = sel_obj.Shape.cut(mortar_compound)
                        if new_shape.isNull():
                            log("ERROR: Boolean cut returned null shape")
                        else:
                            tx_label = f"brick_generator: engrave {obj_name}"
                            doc.openTransaction(tx_label)
                            try:
                                sel_obj.Shape = new_shape
                                doc.recompute()
                                doc.commitTransaction()
                            except Exception:
                                doc.abortTransaction()
                                raise

                            log()
                            log(f"✓ Engraved mortar on: {obj_name}")
                            log(f"  Total bricks: {total_brick_count}")
                            log(f"  Faces processed: {len(faces_processed)}")
                            log(f"  Bond type: {bond_type}")
                            log(f"  Mortar depth: {mortar_depth:.3f}mm")
                            log()
                            log(f"{'='*60}")
                            log(f"SUCCESS!")
                            log(f"{'='*60}")

                    except Exception as e:
                        log(f"\n{'='*60}")
                        log(f"ERROR engraving mortar: {e}")
                        log(f"{'='*60}")
                        import traceback
                        traceback.print_exc()
                else:
                    log("\nERROR: No faces were successfully processed")
            
            else:
                log("ERROR: Please select one or more faces to apply bricks to.")
